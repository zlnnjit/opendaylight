module demo {
    yang-version 1;
    namespace "urn:opendaylight:params:xml:ns:yang:demo";
    prefix "demo";

    revision "2015-01-05" {
        description "Initial revision of demo model";
    }
}
