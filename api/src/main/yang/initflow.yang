module initflow {
    yang-version 1;
    namespace "urn:opendaylight:params:xml:ns:yang:initflow";
    prefix "initflow";

    revision "2015-01-05" {
        description "Initial revision of initflow model";
    }

}
